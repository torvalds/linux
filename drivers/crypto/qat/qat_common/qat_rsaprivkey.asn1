RsaPrivKey ::= SEQUENCE {
	version		INTEGER,
	n		INTEGER ({ qat_rsa_get_n }),
	e		INTEGER ({ qat_rsa_get_e }),
	d		INTEGER ({ qat_rsa_get_d }),
	prime1		INTEGER,
	prime2		INTEGER,
	exponent1	INTEGER,
	exponent2	INTEGER,
	coefficient	INTEGER
}
