GSSAPI ::=
	[APPLICATION 0] IMPLICIT SEQUENCE {
		thisMech
			OBJECT IDENTIFIER ({gssapi_this_mech}),
		negotiationToken
			NegotiationToken
	}

MechType ::= OBJECT IDENTIFIER ({neg_token_init_mech_type})

MechTypeList ::= SEQUENCE OF MechType

NegTokenInit ::=
	SEQUENCE {
		mechTypes
			[0] MechTypeList,
		reqFlags
			[1] BIT STRING OPTIONAL,
		mechToken
			[2] OCTET STRING OPTIONAL ({neg_token_init_mech_token}),
		mechListMIC
			[3] OCTET STRING OPTIONAL
	}

NegTokenTarg ::=
	SEQUENCE {
		negResult
			[0] ENUMERATED OPTIONAL,
		supportedMech
			[1] OBJECT IDENTIFIER OPTIONAL,
		responseToken
			[2] OCTET STRING OPTIONAL ({neg_token_targ_resp_token}),
		mechListMIC
			[3] OCTET STRING OPTIONAL
	}

NegotiationToken ::=
	CHOICE {
		negTokenInit
			[0] NegTokenInit,
		negTokenTarg
			[1] ANY
	}
