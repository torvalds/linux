---
--- ASN.1 for TPM 2.0 keys
---

TPMKey ::= SEQUENCE {
	type		OBJECT IDENTIFIER ({tpm2_key_type}),
	emptyAuth	[0] EXPLICIT BOOLEAN OPTIONAL,
	parent		INTEGER ({tpm2_key_parent}),
	pubkey		OCTET STRING ({tpm2_key_pub}),
	privkey		OCTET STRING ({tpm2_key_priv})
	}
